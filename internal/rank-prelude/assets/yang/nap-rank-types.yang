module nap-rank-types {
    // Header of this document.
    yang-version "1.1";
    namespace "urn:nap:rank";
    prefix "rank";

    import ieee802-dot1q-sched {
        prefix sched;
    }

    import ieee802-dot1q-cbsa {
        prefix cbsa;
    }

    // Revision section.
    organization "Network Architectures and Protocols, Instituto de Telecomunicações, Aveiro";
    contact "ruieduardo.fa.lopes@av.it.pt";
    description "The module for describing Rank protocol data types.";

    revision 2024-01-23 {
        description "Initial version on Rank v0.1.0, revision E";
    }

    // Definitions section.
    container rank-requirement {
        leaf name {
            type string;
        }
        choice requirement {
            case net-bandwidth {
                leaf net-bandwidth {
                    type string;
                }
            }
            case net-dds {
                leaf net-dds {
                    type boolean;
                }
            }
            case time-tas {
                leaf time-tas {
                    type ieee802-dot1q-sched;
                }
            }
            case time-cbs {
                leaf time-cbs {
                    type ieee802-dot1q-cbsa;
                }
            }
            case comp-cpu-usage {
                leaf comp-cpu-usage {
                    type string;
                }
            }
            case comp-memory {
                leaf comp-memory {
                    type string;
                }
            }
        }
    }
}
