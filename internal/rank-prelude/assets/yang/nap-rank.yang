module nap-rank {
    // Header of this document.
    yang-version "1.1";
    namespace "urn:nap:rank";
    prefix "rank";

    import nap-rank-types {
        prefix rank;
    }

    // Revision section.
    organization "Network Architectures and Protocols, Instituto de Telecomunicações, Aveiro";
    contact "ruieduardo.fa.lopes@av.it.pt";
    description "The module for describing requirements to the Rank protocol.";

    revision 2024-01-23 {
        description "Initial version on Rank v0.1.0, revision E";
    }

    // Definitions section.
    container statement {
        list requirements {
            key "requirement";
            leaf requirement {
                type rank-requirement;
            }
        }
    }
}
